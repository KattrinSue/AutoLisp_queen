(defun c:ferz ()
(command "_osnap" "_off")
(setq os (getvar "osmode"))
(setq os3 (getvar "3dosmode"))
(setvar "osmode" 0)
(setvar "3dosmode" 0)
;(command "_view" "_SWISO")
;---------------------------------------------
(initget 7)
(setq nx0 (getreal "\n Укажите начальную координату (например: 1): "))
(initget 7)
(setq ny0 (getreal "\n Укажите начальную координату (например: 1): "))
(initget 7)
(setq nz0 (getreal "\n Укажите начальную координату (например: 1): "))
(initget 7)
(setq k_s (getreal "\n Укажите кол-во сторон основания(от 4 до 20): "))
;(initget 7)
     (while (or (= 1 k_s)(= 2 k_s) (= 3 k_s)(< 20 k_s))
     (princ "\n Ошибка ввода! Кол-во должно быть от 4 до 20")
     (initget 7)
     (setq k_s (getreal "\n Укажите кол-во сторон основания(от 4 до 20): ")))
     (initget 7)
(setq ro_1 (getreal "\n Укажите радиус основания(например: 1000): "))
(initget 7)
(setq ho_1 (getreal "\n Укажите высату основания(например: 250): "))
     (while (or (= ro_1 ho_1)(< ro_1 ho_1))
     (princ "\n Ошибка ввода! Укажите меньше радиуса основания!")
     (initget 7)
     (setq ho_1 (getreal "\n Укажите высату основания(например: 250): ")))
     (initget 7)
;----------------------------------------------
(command "_polygon" k_s (list nx0 ny0 nz0) "" ro_1)
(command "Выдавить" (entlast) "" ho_1)
(setq polygon1 (entlast))
(initget 7)
;---------------------------------------------------------
(setq r_okr_1 (getreal "\n Укажите радиус нижней окружности подставки(например: 800): "))
(initget 7)
(setq r_okr_2 (getreal "\n Укажите радиус верхней окружности подставки(например: 900): "))
     (while (or (= r_okr_1 r_okr_2)(< r_okr_2 r_okr_1))
     (princ "\n Ошибка ввода! Укажите больше нижней окружности подставки!")
     (initget 7)
     (setq r_okr_2 (getreal "\n Укажите радиус верхней окружности подставки(например: 900): ")))
     (initget 7)
(setq h_pod(getreal "\n Укажите высоту подставки(например: 150): "))
     (while (or (= h_pod ho_1)(< ho_1 h_pod))
     (princ "\n Ошибка ввода! Укажите меньше высоты основания!")
     (initget 7)
     (setq h_pod(getreal "\n Укажите высоту подставки(например: 150): ")))
     (initget 7)
;---------------------------------------------------------
(setq ho_1_1 (+ ny0 ho_1))
(setq ho_1_2 (+ ho_1_1 h_pod))
(command "_circle" (list nx0 ny0 ho_1_1) r_okr_1)
(setq circle_1 (entlast))
(command "_circle" (list nx0 ny0 ho_1_2) r_okr_2)
(setq circle_2 (entlast))

(command "_loft" circle_1 circle_2 "" "С")
(setq circle_1a (entlast))
(initget 7)
;---------------------------------------------------------
(setq r_okr_3 (getreal "\n Укажите радиус нижней окружности юбочки(например: 500): "))
(initget 7)
(setq r_okr_4 (getreal "\n Укажите радиус верхней окружности юбочки(например: 800): "))
     (while (or (= r_okr_3 r_okr_4)(< r_okr_4 r_okr_3))
     (princ "\n Ошибка ввода! Укажите больше радиуса нижней окружности юбочки!")
     (initget 7)
     (setq r_okr_4 (getreal "\n Укажите радиус верхней окружности юбочки(например: 800): ")))
     (initget 7)
(setq h_yb(getreal "\n Укажите высоту подставки(например: 400): "))
;---------------------------------------------------------
(setq h_yb1 (+ ho_1_2 h_yb))
(command "_circle" (list nx0 ny0 ho_1_2) r_okr_3)
(setq circle_4 (entlast))
(command "_circle" (list nx0 ny0 h_yb1) r_okr_4)
(setq circle_5 (entlast))
(command "_loft" circle_4 circle_5 "" "С")
(setq circle_2a (entlast))
;---------------------------------------------------------
(setq r_okr_5 (getreal "\n Укажите радиус нижней окружности средней части(например: 700): "))
(initget 7)
(setq r_okr_6 (getreal "\n Укажите радиус верхней средней части(например: 400): "))
     (while (or (= r_okr_5 r_okr_6)(< r_okr_5 r_okr_6))
     (princ "\n Ошибка ввода! Укажите меньше радиуса нижней окружности средней части!")
     (initget 7)
     (setq r_okr_6 (getreal "\n Укажите радиус верхней средней части(например: 400): ")))
     (initget 7)
(setq h_sr_1(getreal "\n Укажите 1-ю высоту средней части(например: 400): "))
(initget 7)
(setq h_sr_2(getreal "\n Укажите 2-ю высоту средней части(например: 1000): "))
     (while (or (= h_sr_1 h_sr_2)(< h_sr_2 h_sr_1))
     (princ "\n Ошибка ввода! Укажите больше 1-й высоты средней части!")
     (initget 7)
     (setq h_sr_2(getreal "\n Укажите 2-ю высоту средней части(например: 1000): ")))
     (initget 7)
;---------------------------------------------------------
(setq h_sr_1_1 (+ h_yb1 h_sr_1))
(setq h_sr_2_1 (+ h_sr_1_1 h_sr_2))
(command "_circle" (list nx0 ny0 h_yb1) r_okr_5)
(setq circle_6 (entlast))
(command "_circle" (list nx0 ny0 h_sr_1_1) r_okr_6)
(setq circle_7 (entlast))
(command "_circle" (list nx0 ny0 h_sr_2_1) r_okr_6)
(setq circle_8 (entlast))
(command "_loft" circle_6 circle_7 circle_8 "" "С")
(setq circle_3a (entlast))
(initget 7)
;--------------------------------------------------------------------------------------------------------
;--------------------------------------------------------------------------------------------------------
(setq k_k (getreal "\n Укажите кол-во колец(от 1 до 3): "))
    (while (or (= 0 k_k)(< 3 k_k))
    (princ "\n Ошибка ввода! Кол-во должно быть от от 1 до 3")
    (initget 7)
    (setq k_k (getreal "\n Укажите кол-во колец(от 1 до 3): ")))
    (initget 7)
;--------------------------------------------------------------------------------------------------------
(if (= k_k 1)
     (prompt
     (setq r_k_1 (getreal "\n Укажите радиус 1-го кольца(например: 500): "))
     (initget 7)
     (setq h_k_1 (getreal "\n Укажите высоту 1-го кольца(например: 150): "))
     (command "_cylinder" (list nx0 ny0 h_sr_2_1) r_k_1 h_k_1)
     (setq cyl_1 (entlast))
;---------------------------------------------------------
     (setq h_chast_1 (+ h_sr_2_1 h_k_1))
     (initget 7)
     (setq r_okr_7 (getreal "\n Укажите 1-й радиус верхней чати(например: 200): "))
     	(while (or (= r_okr_7 r_k_1)(< r_k_1 r_okr_7))
     	(princ "\n Ошибка ввода! Укажите меньше радиуса кольца")
     	(initget 7)
     	(setq r_okr_7 (getreal "\n Укажите 1-й радиус верхней чати(например: 200): ")))
     	(initget 7)
     (setq h_okr_7 (getreal "\n Укажите 1-ю высоту верхней чати(например: 300): "))
     (initget 7)
     (setq r_okr_8 (getreal "\n Укажите 2-й радиус верхней чати(например: 250): "))
     	(while (or (= r_okr_7 r_okr_8)(< r_okr_8 r_okr_7))
     	(princ "\n Ошибка ввода! Укажите больше 1-го радиуса верхней чати")
     	(initget 7)
     	(setq r_okr_8 (getreal "\n Укажите 2-й радиус верхней чати(например: 250): ")))
     	(initget 7)
     (setq h_okr_8 (getreal "\n Укажите 2-ю высоту верхней чати(например: 150): "))
     (initget 7)
     (setq r_okr_9 (getreal "\n Укажите 3-й радиус верхней чати(например: 350): "))
        (while (or (= r_okr_9 r_okr_8)(< r_okr_9 r_okr_8))
     	(princ "\n Ошибка ввода! Укажите больше 2-го радиуса верхней чати")
     	(initget 7)
     	(setq r_okr_9 (getreal "\n Укажите 3-й радиус верхней чати(например: 350): ")))
     	(initget 7)
     (setq h_okr_9 (getreal "\n Укажите 3-ю высоту верхней чати(например: 150): "))
     (initget 7)
     (setq r_okr_10 (getreal "\n Укажите 4-й радиус верхней чати(например: 300): "))
        (while (or (= r_okr_9 r_okr_10)(< r_okr_9 r_okr_10))
     	(princ "\n Ошибка ввода! Укажите меньше 3-го радиуса верхней чати")
     	(initget 7)
     	(setq r_okr_10 (getreal "\n Укажите 3-й радиус верхней чати(например: 300): ")))
     	(initget 7)
;---------------------------------------------------------
      (command "_circle" (list nx0 ny0 h_chast_1) r_okr_7)
      (setq circle_9 (entlast))
      (setq h_chast_2 (+ h_chast_1 h_okr_7))
      (setq h_chast_3 (+ h_chast_2 h_okr_8))
      (setq h_chast_4 (+ h_chast_3 h_okr_9))
      (command "_circle" (list nx0 ny0 h_chast_2) r_okr8)
      (setq circle_10 (entlast))
      (command "_circle" (list nx0 ny0 h_chast_3) r_okr_9)
      (setq circle_11 (entlast))
      (command "_circle" (list nx0 ny0 h_chast_4) r_okr_10)
      (setq circle_12 (entlast))
      (command "_loft" circle_9 circle_10 circle_11 circle_12 "" "С")
      (setq circle_4a (entlast))
;---------------------------------------------------------
      (setq r_sph_1 (getreal "\n Укажите радиус сферы(например: 250): "))
      (initget 7)
      	(while (or (= r_sph_1 r_okr_10)(< r_okr_10 r_sph_1))
     	(princ "\n Ошибка ввода! Укажите меньше 4-го радиуса верхней чати")
     	(initget 7)
     	(setq r_sph_1 (getreal "\n Укажите радиус сферы(например: 250): ")))
     	(initget 7)
      (command "_sphere" (list nx0 ny0 h_chast_4) r_sph_1)
      (setq sphere_1 (entlast))
;---------------------------------------------------------
(setq r_nogi (getreal "\n Укажите радиус ножки(например: 50): "))
	(while (or (= r_sph_1 r_nogi)(< r_sph_1 r_nogi))
     	(princ "\n Ошибка ввода! Укажите меньше радиуса сферы чати")
     	(initget 7)
     	(setq r_nogi (getreal "\n Укажите радиус ножки(например: 50): ")))
     	(initget 7)
(setq h_nogi_1 (getreal "\n Укажите высоту ножки(например: 50): "))
(while (or (= r_sph_1 h_nogi_1)(< r_sph_1 h_nogi_1))
     	(princ "\n Ошибка ввода! Укажите меньше радиуса сферы")
     	(initget 7)
     	(setq h_nogi_1 (getreal "\n Укажите высоту ножки(например: 50): ")))
     	(initget 7)
(setq h_nogi (+ h_chast_4 r_sph_1))
(command "_cylinder" (list nx0 ny0 h_nogi) r_nogi h_nogi_1)
(setq cyl_4 (entlast))
;---------------------------------------------------------
(setq r_pim_1 (getreal "\n Укажите 1-й радиус пимпочки(например: 75): "))
(while (or (<= (* r_nogi 2) r_pim_1))
     	(princ "\n Ошибка ввода! Укажите меньше радиуса сферы")
     	(initget 7)
     	(setq r_pim_1 (getreal "\n Укажите 1-й радиус пимпочки(например: 75): ")))
     	(initget 7)
(setq h_pim_1_1 (getreal "\n Укажите 1-ю высоту пимпочки(например: 25): "))
(while (or (< (/ h_nogi 2) h_pim_1_1))
     	(princ "\n Ошибка ввода! Укажите не больше половины высоты ножки")
     	(initget 7)
     	(setq h_pim_1_1 (getreal "\n Укажите 1-ю высоту пимпочки(например: 25): ")))
     	(initget 7)
(setq r_pim_2 (getreal "\n Укажите 2-й радиус пимпочки(например: 100): "))
(while (or (< r_pim_2 r_pim_1))
     	(princ "\n Ошибка ввода! Укажите больше 1-го радиуса пимпочки!")
     	(initget 7)
     	(setq r_pim_2 (getreal "\n Укажите 2-й радиус пимпочки(например: 100): ")))
     	(initget 7)
(setq h_pim_2_1 (getreal "\n Укажите 2-ю высоту пимпочки(например: 25): "))
(while (or (< h_pim_1_1 h_pim_1_2))
     	(princ "\n Ошибка ввода! Укажите не больше 1-й высоты пимпочки!")
     	(initget 7)
     	(setq h_pim_2_1 (getreal "\n Укажите 2-ю высоту пимпочки(например: 25): ")))
     	(initget 7)
(setq r_pim_3 (getreal "\n Укажите 3-й радиус пимпочки(например: 50): "))
(while (or (< r_pim_2 r_pim_3))
     	(princ "\n Ошибка ввода! Укажите меньше 2-го радиуса пимпочки!")
     	(initget 7)
     	(setq r_pim_3 (getreal "\n Укажите 3-й радиус пимпочки(например: 50): ")))
     	(initget 7)


(setq h_pim_1 (+ h_nogi h_nogi_1))
(setq h_pim_2 (+ h_pim_1 h_pim_1_1))
(setq h_pim_3 (+ h_pim_2 h_pim_2_1))
(command "_circle" (list nx0 ny0 h_pim_1) r_pim_1)
(setq circle_13 (entlast))
(command "_circle" (list nx0 ny0 h_pim_2) r_pim_2)
(setq circle_14 (entlast))
(command "_circle" (list nx0 ny0 h_pim_3) r_pim_3)
(setq circle_15 (entlast))
(command "_loft" circle_13 circle_14 circle_15 "" "С")
(setq circle_5a (entlast))
  )
 )
  ;---------------------------------------------------------

  (if (= k_k 2)
   (prompt
  (setq r_k_1 (getreal "\n Укажите радиус 1-го кольца(например: 500): "))
  (initget 7)
  (setq h_k_1 (getreal "\n Укажите высоту 1-го кольца(например: 150): "))
  (command "_cylinder" (list nx0 ny0 h_sr_2_1) r_k_1 h_k_1)
  (setq cyl_1 (entlast))

  (setq h_kol_1 (+ h_sr_2_1 h_k_1))
  (setq r_k_2 (getreal "\n Укажите радиус 2-го кольца(например: 400): "))
  (while (or (< r_k_1 r_k_2))
     	(princ "\n Ошибка ввода! Укажите меньше радиуса 1-го кольца!")
     	(initget 7)
     	(setq r_k_2 (getreal "\n Укажите радиус 2-го кольца(например: 400): ")))
     	(initget 7)
  (setq h_k_2 (getreal "\n Укажите высоту 2-го кольца(например: 100): "))
  (command "_cylinder" (list nx0 ny0 h_kol_1) r_k_2 h_k_2)
  (setq cyl_2 (entlast))

    (setq h_chast_1 (+ h_kol_1 h_k_2))
   (initget 7)
     (setq r_okr_7 (getreal "\n Укажите 1-й радиус верхней чати(например: 200): "))
     	(while (or (= r_okr_7 r_k_1)(< r_k_1 r_okr_7))
     	(princ "\n Ошибка ввода! Укажите меньше радиуса кольца")
     	(initget 7)
     	(setq r_okr_7 (getreal "\n Укажите 1-й радиус верхней чати(например: 200): ")))
     	(initget 7)
     (setq h_okr_7 (getreal "\n Укажите 1-ю высоту верхней чати(например: 300): "))
     (initget 7)
     (setq r_okr_8 (getreal "\n Укажите 2-й радиус верхней чати(например: 250): "))
     	(while (or (= r_okr_7 r_okr_8)(< r_okr_8 r_okr_7))
     	(princ "\n Ошибка ввода! Укажите больше 1-го радиуса верхней чати")
     	(initget 7)
     	(setq r_okr_8 (getreal "\n Укажите 2-й радиус верхней чати(например: 250): ")))
     	(initget 7)
     (setq h_okr_8 (getreal "\n Укажите 2-ю высоту верхней чати(например: 150): "))
     (initget 7)
     (setq r_okr_9 (getreal "\n Укажите 3-й радиус верхней чати(например: 350): "))
        (while (or (= r_okr_9 r_okr_8)(< r_okr_9 r_okr_8))
     	(princ "\n Ошибка ввода! Укажите больше 2-го радиуса верхней чати")
     	(initget 7)
     	(setq r_okr_9 (getreal "\n Укажите 3-й радиус верхней чати(например: 350): ")))
     	(initget 7)
     (setq h_okr_9 (getreal "\n Укажите 3-ю высоту верхней чати(например: 150): "))
     (initget 7)
     (setq r_okr_10 (getreal "\n Укажите 4-й радиус верхней чати(например: 300): "))
        (while (or (= r_okr_9 r_okr_10)(< r_okr_9 r_okr_10))
     	(princ "\n Ошибка ввода! Укажите меньше 3-го радиуса верхней чати")
     	(initget 7)
     	(setq r_okr_10 (getreal "\n Укажите 3-й радиус верхней чати(например: 300): ")))
     	(initget 7)
;---------------------------------------------------------
      (command "_circle" (list nx0 ny0 h_chast_1) r_okr_7)
      (setq circle_9 (entlast))
      (setq h_chast_2 (+ h_chast_1 h_okr_7))
      (setq h_chast_3 (+ h_chast_2 h_okr_8))
      (setq h_chast_4 (+ h_chast_3 h_okr_9))
      (command "_circle" (list nx0 ny0 h_chast_2) r_okr8)
      (setq circle_10 (entlast))
      (command "_circle" (list nx0 ny0 h_chast_3) r_okr_9)
      (setq circle_11 (entlast))
      (command "_circle" (list nx0 ny0 h_chast_4) r_okr_10)
      (setq circle_12 (entlast))
      (command "_loft" circle_9 circle_10 circle_11 circle_12 "" "С")
      (setq circle_4a (entlast))
;---------------------------------------------------------
      (setq r_sph_1 (getreal "\n Укажите радиус сферы(например: 250): "))
      (initget 7)
      	(while (or (= r_sph_1 r_okr_10)(< r_okr_10 r_sph_1))
     	(princ "\n Ошибка ввода! Укажите меньше 4-го радиуса верхней чати")
     	(initget 7)
     	(setq r_sph_1 (getreal "\n Укажите радиус сферы(например: 250): ")))
     	(initget 7)
      (command "_sphere" (list nx0 ny0 h_chast_4) r_sph_1)
      (setq sphere_1 (entlast))
;---------------------------------------------------------
(setq r_nogi (getreal "\n Укажите радиус ножки(например: 50): "))
	(while (or (= r_sph_1 r_nogi)(< r_sph_1 r_nogi))
     	(princ "\n Ошибка ввода! Укажите меньше радиуса сферы чати")
     	(initget 7)
     	(setq r_nogi (getreal "\n Укажите радиус ножки(например: 50): ")))
     	(initget 7)
(setq h_nogi_1 (getreal "\n Укажите высоту ножки(например: 50): "))
(while (or (= r_sph_1 h_nogi_1)(< r_sph_1 h_nogi_1))
     	(princ "\n Ошибка ввода! Укажите меньше радиуса сферы")
     	(initget 7)
     	(setq h_nogi_1 (getreal "\n Укажите высоту ножки(например: 50): ")))
     	(initget 7)
(setq h_nogi (+ h_chast_4 r_sph_1))
(command "_cylinder" (list nx0 ny0 h_nogi) r_nogi h_nogi_1)
(setq cyl_4 (entlast))
;---------------------------------------------------------
(setq r_pim_1 (getreal "\n Укажите 1-й радиус пимпочки(например: 75): "))
(while (or (<= (* r_nogi 2) r_pim_1))
     	(princ "\n Ошибка ввода! Укажите меньше радиуса сферы")
     	(initget 7)
     	(setq r_pim_1 (getreal "\n Укажите 1-й радиус пимпочки(например: 75): ")))
     	(initget 7)
(setq h_pim_1_1 (getreal "\n Укажите 1-ю высоту пимпочки(например: 25): "))
(while (or (< (/ h_nogi 2) h_pim_1_1))
     	(princ "\n Ошибка ввода! Укажите не больше половины высоты ножки")
     	(initget 7)
     	(setq h_pim_1_1 (getreal "\n Укажите 1-ю высоту пимпочки(например: 25): ")))
     	(initget 7)
(setq r_pim_2 (getreal "\n Укажите 2-й радиус пимпочки(например: 100): "))
(while (or (< r_pim_2 r_pim_1))
     	(princ "\n Ошибка ввода! Укажите больше 1-го радиуса пимпочки!")
     	(initget 7)
     	(setq r_pim_2 (getreal "\n Укажите 2-й радиус пимпочки(например: 100): ")))
     	(initget 7)
(setq h_pim_2_1 (getreal "\n Укажите 2-ю высоту пимпочки(например: 25): "))
(while (or (< h_pim_1_1 h_pim_1_2))
     	(princ "\n Ошибка ввода! Укажите не больше 1-й высоты пимпочки!")
     	(initget 7)
     	(setq h_pim_2_1 (getreal "\n Укажите 2-ю высоту пимпочки(например: 25): ")))
     	(initget 7)
(setq r_pim_3 (getreal "\n Укажите 3-й радиус пимпочки(например: 50): "))
(while (or (< r_pim_2 r_pim_3))
     	(princ "\n Ошибка ввода! Укажите меньше 2-го радиуса пимпочки!")
     	(initget 7)
     	(setq r_pim_3 (getreal "\n Укажите 3-й радиус пимпочки(например: 50): ")))
     	(initget 7)


(setq h_pim_1 (+ h_nogi h_nogi_1))
(setq h_pim_2 (+ h_pim_1 h_pim_1_1))
(setq h_pim_3 (+ h_pim_2 h_pim_2_1))
(command "_circle" (list nx0 ny0 h_pim_1) r_pim_1)
(setq circle_13 (entlast))
(command "_circle" (list nx0 ny0 h_pim_2) r_pim_2)
(setq circle_14 (entlast))
(command "_circle" (list nx0 ny0 h_pim_3) r_pim_3)
(setq circle_15 (entlast))
(command "_loft" circle_13 circle_14 circle_15 "" "С")
(setq circle_5a (entlast))
  )
 )
  ;---------------------------------------------------------

  (if (= k_k 3)
   (prompt
  (setq r_k_1 (getreal "\n Укажите радиус 1-го кольца(например: 500): "))
  (initget 7)
  (setq h_k_1 (getreal "\n Укажите высоту 1-го кольца(например: 150): "))
  (command "_cylinder" (list nx0 ny0 h_sr_2_1) r_k_1 h_k_1)
  (setq cyl_1 (entlast))

  (setq h_kol_1 (+ h_sr_2_1 h_k_1))
  (setq r_k_2 (getreal "\n Укажите радиус 2-го кольца(например: 400): "))
  (while (or (< r_k_1 r_k_2))
     	(princ "\n Ошибка ввода! Укажите меньше радиуса 1-го кольца!")
     	(initget 7)
     	(setq r_k_2 (getreal "\n Укажите радиус 2-го кольца(например: 400): ")))
     	(initget 7)
  (setq h_k_2 (getreal "\n Укажите высоту 2-го кольца(например: 100): "))
  (command "_cylinder" (list nx0 ny0 h_kol_1) r_k_2 h_k_2)
  (setq cyl_2 (entlast))
      
  (setq h_kol_2 (+ h_kol_1 h_k_2))
  (setq r_k_3 (getreal "\n Укажите радиус 3-го кольца(например: 300): "))
  (while (or (< r_k_2 r_k_3))
     	(princ "\n Ошибка ввода! Укажите меньше радиуса 2-го кольца!")
     	(initget 7)
     	(setq r_k_3 (getreal "\n Укажите радиус 3-го кольца(например: 300): ")))
     	(initget 7)
  (setq h_k_3 (getreal "\n Укажите высоту 3-го кольца(например: 50): "))
  (command "_cylinder" (list nx0 ny0 h_kol_2) r_k_3 h_k_3)
  (setq cyl_3 (entlast))

  (setq h_chast_1 (+ h_kol_2 h_k_3))
   (initget 7)
     (setq r_okr_7 (getreal "\n Укажите 1-й радиус верхней чати(например: 200): "))
     	(while (or (= r_okr_7 r_k_1)(< r_k_1 r_okr_7))
     	(princ "\n Ошибка ввода! Укажите меньше радиуса кольца")
     	(initget 7)
     	(setq r_okr_7 (getreal "\n Укажите 1-й радиус верхней чати(например: 200): ")))
     	(initget 7)
     (setq h_okr_7 (getreal "\n Укажите 1-ю высоту верхней чати(например: 300): "))
     (initget 7)
     (setq r_okr_8 (getreal "\n Укажите 2-й радиус верхней чати(например: 250): "))
     	(while (or (= r_okr_7 r_okr_8)(< r_okr_8 r_okr_7))
     	(princ "\n Ошибка ввода! Укажите больше 1-го радиуса верхней чати")
     	(initget 7)
     	(setq r_okr_8 (getreal "\n Укажите 2-й радиус верхней чати(например: 250): ")))
     	(initget 7)
     (setq h_okr_8 (getreal "\n Укажите 2-ю высоту верхней чати(например: 150): "))
     (initget 7)
     (setq r_okr_9 (getreal "\n Укажите 3-й радиус верхней чати(например: 350): "))
        (while (or (= r_okr_9 r_okr_8)(< r_okr_9 r_okr_8))
     	(princ "\n Ошибка ввода! Укажите больше 2-го радиуса верхней чати")
     	(initget 7)
     	(setq r_okr_9 (getreal "\n Укажите 3-й радиус верхней чати(например: 350): ")))
     	(initget 7)
     (setq h_okr_9 (getreal "\n Укажите 3-ю высоту верхней чати(например: 150): "))
     (initget 7)
     (setq r_okr_10 (getreal "\n Укажите 4-й радиус верхней чати(например: 300): "))
        (while (or (= r_okr_9 r_okr_10)(< r_okr_9 r_okr_10))
     	(princ "\n Ошибка ввода! Укажите меньше 3-го радиуса верхней чати")
     	(initget 7)
     	(setq r_okr_10 (getreal "\n Укажите 3-й радиус верхней чати(например: 300): ")))
     	(initget 7)
      (command "_circle" (list nx0 ny0 h_chast_1) r_okr_7)
      (setq circle_9 (entlast))
      (setq h_chast_2 (+ h_chast_1 h_okr_7))
      (setq h_chast_3 (+ h_chast_2 h_okr_8))
      (setq h_chast_4 (+ h_chast_3 h_okr_9))
      (command "_circle" (list nx0 ny0 h_chast_2) r_okr8)
      (setq circle_10 (entlast))
      (command "_circle" (list nx0 ny0 h_chast_3) r_okr_9)
      (setq circle_11 (entlast))
      (command "_circle" (list nx0 ny0 h_chast_4) r_okr_10)
      (setq circle_12 (entlast))
      (command "_loft" circle_9 circle_10 circle_11 circle_12 "" "С")
      (setq circle_4a (entlast))
;---------------------------------------------------------
      (setq r_sph_1 (getreal "\n Укажите радиус сферы(например: 250): "))
      (initget 7)
      	(while (or (= r_sph_1 r_okr_10)(< r_okr_10 r_sph_1))
     	(princ "\n Ошибка ввода! Укажите меньше 4-го радиуса верхней чати")
     	(initget 7)
     	(setq r_sph_1 (getreal "\n Укажите радиус сферы(например: 250): ")))
     	(initget 7)
      (command "_sphere" (list nx0 ny0 h_chast_4) r_sph_1)
      (setq sphere_1 (entlast))
;---------------------------------------------------------
(setq r_nogi (getreal "\n Укажите радиус ножки(например: 50): "))
	(while (or (= r_sph_1 r_nogi)(< r_sph_1 r_nogi))
     	(princ "\n Ошибка ввода! Укажите меньше радиуса сферы чати")
     	(initget 7)
     	(setq r_nogi (getreal "\n Укажите радиус ножки(например: 50): ")))
     	(initget 7)
(setq h_nogi_1 (getreal "\n Укажите высоту ножки(например: 50): "))
(while (or (= r_sph_1 h_nogi_1)(< r_sph_1 h_nogi_1))
     	(princ "\n Ошибка ввода! Укажите меньше радиуса сферы")
     	(initget 7)
     	(setq h_nogi_1 (getreal "\n Укажите высоту ножки(например: 50): ")))
     	(initget 7)
(setq h_nogi (+ h_chast_4 r_sph_1))
(command "_cylinder" (list nx0 ny0 h_nogi) r_nogi h_nogi_1)
(setq cyl_4 (entlast))
;---------------------------------------------------------
(setq r_pim_1 (getreal "\n Укажите 1-й радиус пимпочки(например: 75): "))
(while (or (<= (* r_nogi 2) r_pim_1))
     	(princ "\n Ошибка ввода! Укажите меньше радиуса сферы")
     	(initget 7)
     	(setq r_pim_1 (getreal "\n Укажите 1-й радиус пимпочки(например: 75): ")))
     	(initget 7)
(setq h_pim_1_1 (getreal "\n Укажите 1-ю высоту пимпочки(например: 25): "))
(while (or (< (/ h_nogi 2) h_pim_1_1))
     	(princ "\n Ошибка ввода! Укажите не больше половины высоты ножки")
     	(initget 7)
     	(setq h_pim_1_1 (getreal "\n Укажите 1-ю высоту пимпочки(например: 25): ")))
     	(initget 7)
(setq r_pim_2 (getreal "\n Укажите 2-й радиус пимпочки(например: 100): "))
(while (or (< r_pim_2 r_pim_1))
     	(princ "\n Ошибка ввода! Укажите больше 1-го радиуса пимпочки!")
     	(initget 7)
     	(setq r_pim_2 (getreal "\n Укажите 2-й радиус пимпочки(например: 100): ")))
     	(initget 7)
(setq h_pim_2_1 (getreal "\n Укажите 2-ю высоту пимпочки(например: 25): "))
(while (or (< h_pim_1_1 h_pim_1_2))
     	(princ "\n Ошибка ввода! Укажите не больше 1-й высоты пимпочки!")
     	(initget 7)
     	(setq h_pim_2_1 (getreal "\n Укажите 2-ю высоту пимпочки(например: 25): ")))
     	(initget 7)
(setq r_pim_3 (getreal "\n Укажите 3-й радиус пимпочки(например: 50): "))
(while (or (< r_pim_2 r_pim_3))
     	(princ "\n Ошибка ввода! Укажите меньше 2-го радиуса пимпочки!")
     	(initget 7)
     	(setq r_pim_3 (getreal "\n Укажите 3-й радиус пимпочки(например: 50): ")))
     	(initget 7)
(setq h_pim_1 (+ h_nogi h_nogi_1))
(setq h_pim_2 (+ h_pim_1 h_pim_1_1))
(setq h_pim_3 (+ h_pim_2 h_pim_2_1))
(command "_circle" (list nx0 ny0 h_pim_1) r_pim_1)
(setq circle_13 (entlast))
(command "_circle" (list nx0 ny0 h_pim_2) r_pim_2)
(setq circle_14 (entlast))
(command "_circle" (list nx0 ny0 h_pim_3) r_pim_3)
(setq circle_15 (entlast))
(command "_loft" circle_13 circle_14 circle_15 "" "С")
(setq circle_5a (entlast))
  )
 )
;---------------------------------------------------------


  (setvar "osmode" os)
  (setvar "3dosmode" os3)
)
